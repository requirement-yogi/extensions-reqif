# test

## REQIF-0011 (Requirement Type 1 b>Trick/b> <b>Trick2)
hello
world

## REQIF-0011 b>Trick/b> <b>Trick2 (Requirement Type 1 b>Trick/b> <b>Trick2)
1.9
- SpecRelation Type -> REQIF-0012

## REQIF-0012 (Requirement Type 1 b>Trick/b> <b>Trick2)
1.2

## REQIF-0013 (Requirement Type 1 b>Trick/b> <b>Trick2)
1.3
- SpecRelation Type -> REQIF-0012

## REQIF-0021 (Requirement Type 2)
2.1

## REQIF-0022 (Requirement Type 2)
2.2

## REQIF-0023 (Requirement Type 2)
2.3

## REQIF-0031 (Requirement Type 3)
3.1
- SpecRelation Type -> REQIF-0011

## REQIF-0032 (Requirement Type 3)
3.2

## REQIF-0033 (Requirement Type 3)
3.3

## 41000001 (Requirement Type 1 - 4)
4.1
- REQIF-0041

## 41000002 (Requirement Type 1 b>Trick/b> <b>Trick2)
4.2
- REQIF-0042

## REQIF-0011 (Requirement Type 1 b>Trick/b> <b>Trick2)
1.4
