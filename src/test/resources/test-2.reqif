# Specification: Specification Document
- Description: Requirements Document

## R5: User-Friendly Searcing Title (Requirement Type)

### R1 (Requirement Type)
While there is ✔  ! " # $ % & ' ( ) * + , - . / 0 1 2 3 4 5 6 7 8 9 : ; < = > ? @ A B C D E F G H I J K L M N O P Q R S T U V W X Y Z [ \ ] ^ _ ` ` Single quote / backtick   HTML Character Entities 2 a b c d e f g h i j k l m n o p q r s t u v w x y z { | } ~    ¡ ¢ £ ¤ ¥ ¦ § ¨ © ª « ¬ ­ ® ¯ ° ± ² ³ ´ µ ¶ · ¸ ¹ º » ¼ ½ ½ One half    HTML Character Entities 3 ¾ ¿ À Á Â Ã Ä Å Æ Ç È É Ê Ë Ì Í Î Ï Ð Ñ Ò Ó Ô Õ Ö × Ø Ù Ú Û Ü Ý Þ ß à á â ã ä å æ ç è é ê ë ì í î ï ð ñ ò ó ô õ ö ÷ ø ù ú û ü ý þ þ ÿÿ very basic search support available, it is currently not suitable for professional work.  The objective of this project is to improve this, as follows:
- Boolean: true
- Due: 2080-12-08T13:48:00.220+01:00
- Real: 1.7854

### R7: Search-UI (Requirement Type)

#### R2 (Requirement Type)
The following is a proposal on how the interface could look like, based on best practices in user interface design.
- Status: Done
- Integer: 1

#### R6 (Information Type)
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✔ ! " # $ % & ' ( ) * + , - . / 0 1 2 3 4 5 6 7 8 9 : ; < = > ? @ A B C D E F G H I J K L M N O P Q R S T U V W X Y Z [ \ ] ^ _ ` ` Single quote / backtick HTML Character Entities 2 a b c d e f g h i j k l m n o p q r s t u v w x y z { | } ~  ¡ ¢ £ ¤ ¥ ¦ § ¨ © ª « ¬ ­ ® ¯ ° ± ² ³ ´ µ ¶ · ¸ ¹ º » ¼ ½ ½ One half HTML Character Entities 3 ¾ ¿ À Á Â Ã Ä Å Æ Ç È É Ê Ë Ì Í Î Ï Ð Ñ Ò Ó Ô Õ Ö × Ø Ù Ú Û Ü Ý Þ ß à á â ã ä å æ ç è é ê ë ì í î ï ð ñ ò ó ô õ ö ÷ ø ù ú û ü ý þ þ ÿÿ very
Description
ᚠᛇᚻ᛫ᛒᛦᚦ᛫ᚠᚱᚩᚠᚢᚱ᛫ᚠᛁᚱᚪ᛫ᚷᛖᚻᚹᛦᛚᚳᚢᛗ
An preost wes on leoden, Laȝamon was ihoten
Sîne klâwen durh die wolken sint geslagen,
Τη γλώσσα μου έδωσαν ελληνική
Τὴ γλῶσσα μοῦ ἔδωσαν ἑλληνικὴ
На берегу пустынных волн
ვეპხის ტყაოსანი შოთა რუსთაველი
யாமறிந்த மொழிகளிலே தமிழ்மொழி போ
ಬಾ ಇಲ್ಲಿ ಸಂಭವಿಸು ಇಂದೆನ್ನ ಹೃದಯದ
Sanskrit: ﻿काचं शक्नोम्यत्तुम् । नोपहिनस्ति माम् ॥
Sanskrit (standard transcription): kācaṃ śaknomyattum; nopahinasti mām.
Classical Greek: ὕαλον ϕαγεῖν δύναμαι· τοῦτο οὔ με βλάπτει.
Greek (monotonic): Μπορώ να φάω σπασμένα γυαλιά χωρίς να πάθω τίποτα.
Greek (polytonic): Μπορῶ νὰ φάω σπασμένα γυαλιὰ χωρὶς νὰ πάθω τίποτα.
Nórdicg: Ljœr ye caudran créneþ ý jor cẃran.
Lojban: mi kakne le nu citka le blaci .iku'i le se go'i na xrani mi
Tibetan: ཤེལ་སྒོ་ཟ་ནས་ང་ན་གི་མ་རེད།
Chinese: 我能吞下玻璃而不伤身体。
Chinese (Traditional): 我能吞下玻璃而不傷身體。
Japanese: 私はガラスを食べられます。それは私を傷つけません。
Korean: 나는 유리를 먹을 수 있어요. 그래도 아프지 않아요
Marquesan: E koʻana e kai i te karahi, mea ʻā, ʻaʻe hauhau.
Inuktitut (10): ᐊᓕᒍᖅ ᓂᕆᔭᕌᖓᒃᑯ ᓱᕋᙱᑦᑐᓐᓇᖅᑐᖓ
Khmer: ខ្ញុំអាចញុំកញ្ចក់បាន ដោយគ្មានបញ្ហារ
Lao: ຂອ້ຍກິນແກ້ວໄດ້ໂດຍທີ່ມັນບໍ່ໄດ້ເຮັດໃຫ້ຂອ້ຍເຈັບ.
Thai: ฉันกินกระจกได้ แต่มันไม่ทำให้ฉันเจ็บ
Mongolian (Cyrillic): Би шил идэй чадна, надад хортой биш
Mongolian (Classic) (5): ᠪᠢ ᠰᠢᠯᠢ ᠢᠳᠡᠶᠦ ᠴᠢᠳᠠᠨᠠ ᠂ ᠨᠠᠳᠤᠷ ᠬᠣᠤᠷᠠᠳᠠᠢ ᠪᠢᠰᠢ
Nepali: ﻿म काँच खान सक्छू र मलाई केहि नी हुन्‍न् ।
Hausa (Latin): Inā iya taunar gilāshi kuma in gamā lāfiyā.
Hausa (Ajami) (2): إِنا إِىَ تَونَر غِلَاشِ كُمَ إِن غَمَا لَافِىَا
Burmese: က္ယ္ဝန္‌တော္‌၊က္ယ္ဝန္‌မ မ္ယက္‌စားနုိင္‌သည္‌။ ၎က္ရောင္‌့ ထိခုိက္‌မ္ဟု မရ္ဟိပာ။ (9)
Vietnamese (quốc ngữ): Tôi có thể ăn thủy tinh mà không hại gì.
Vietnamese (nôm) (4): 些 ࣎ 世 咹 水 晶 ও 空 ࣎ 害 咦
Urdu(3): میں کانچ کھا سکتا ہوں اور مجھے تکلیف نہیں ہوتی ۔
Pashto(3): زه شيشه خوړلې شم، هغه ما نه خوږوي
Farsi / Persian(3): .من می توانم بدونِ احساس درد شيشه بخورم
Arabic(3): أنا قادر على أكل الزجاج و هذا لا يؤلمني.
Maltese: Nista' niekol il-ħġieġ u ma jagħmilli xejn.
Hebrew(3): אני יכול לאכול זכוכית וזה לא מזיק לי.
Yiddish(3): איך קען עסן גלאָז און עס טוט מיר נישט װײ.
Twi: Metumi awe tumpan, ɜnyɜ me hwee.
Kannada: ನನಗೆ ಹಾನಿ ಆಗದೆ, ನಾನು ಗಜನ್ನು ತಿನಬಹುದು
Hindi: मैं काँच खा सकता हूँ और मुझे उससे कोई चोट नहीं पहुंचती.
Tamil: நான் கண்ணாடி சாப்பிடுவேன், அதனால் எனக்கு ஒரு கேடும் வராது.
Telugu: నేను గాజు తినగలను మరియు అలా చేసినా నాకు ఏమి ఇబ్బంది లేదు
Sinhalese: මට වීදුරු කෑමට හැකියි. එයින් මට කිසි හානියක් සිදු නොවේ.
Russian: Я могу есть стекло, оно мне не вредит.
Georgian: მინას ვჭამ და არა მტკივა.
Armenian: Կրնամ ապակի ուտել և ինծի անհանգիստ չըներ։
Albanian: Unë mund të ha qelq dhe nuk më gjen gjë.
Turkish (Ottoman): جام ييه بلورم بڭا ضررى طوقونمز
Bangla / Bengali: আমি কাঁচ খেতে পারি, তাতে আমার কোনো ক্ষতি হয় না।
Marathi: मी काच खाऊ शकतो, मला ते दुखत नाही.
Anglo-Saxon (Runes): ᛁᚳ᛫ᛗᚨᚷ᛫ᚷᛚᚨᛋ᛫ᛖᚩᛏᚪᚾ᛫ᚩᚾᛞ᛫ᚻᛁᛏ᛫ᚾᛖ᛫ᚻᛖᚪᚱᛗᛁᚪᚧ᛫ᛗᛖ᛬
English (IPA): [aɪ kæn iːt glɑːs ænd ɪt dɐz nɒt hɜːt miː] (Received Pronunciation)
English (Braille): ⠊⠀⠉⠁⠝⠀⠑⠁⠞⠀⠛⠇⠁⠎⠎⠀⠁⠝⠙⠀⠊⠞⠀⠙⠕⠑⠎⠝⠞⠀⠓⠥⠗⠞⠀⠍⠑
Gothic (4): ЌЌЌ ЌЌЌЍ Ќ̈ЍЌЌ, ЌЌ ЌЌЍ ЍЌ ЌЌЌЌ ЌЍЌЌЌЌЌ.
Old Norse (Runes): ᛖᚴ ᚷᛖᛏ ᛖᛏᛁ ᚧ ᚷᛚᛖᚱ ᛘᚾ ᚦᛖᛋᛋ ᚨᚧ ᚡᛖ ᚱᚧᚨ ᛋᚨᚱ
Bosnian, Montenegrin and Serbian (Cyrillic): Ја могу јести стакло, и то ми не штети.
See http://www.columbia.edu/~fdc/utf8/index.html

#### R8 (Requirement Type)
Note that this is a non-functional mock-up.  The final interface will differ in appearance.
- Status: Done

#### R9 (Requirement Type)
The final Details regarding the conditions are found after this table in “Search Conditions” below. interface will differ in appearance.
- Status: Done

#### R10 (Requirement Type)
The search interface allows the user to to configure a number of “conditions”.  These relate either to internal attributes (e.g. internal ID) or attribute values (those attributes that the user creates), with typical type-specific relations: equal, contains, etc.
- Status: Done

#### R11 (Requirement Type)
All conditions are combined via “and” or “or”.  More complex relationships are not supported in this first implementation. Details regarding the conditions are found after this table in “Search Conditions” below.
- Status: Done

### R12: Spec-Nav (Requirement Type)

#### Spec-Nav (Requirement Type)
Within a Specification, users can navigate between search results via corresponding buttons in the toolbar, i.e. .  Note that this will not cycle through elements outside the specification (e.g. elements in other Specifications or SpecTypes).
- Status: Done

#### R13 (Information Type)
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
### R14: Result-Nav (Requirement Type)

#### Result-Nav (Requirement Type)
The result of a search will be shown in a separate view, as shown in the mockup (implementation appearance may vary).
- Status: Done

#### R19 (Information Type)
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
#### R15 (Requirement Type)
In will show all matches, including those that are not accessible from the Specification Editor.
- Status: Done

#### R16 (Requirement Type)
The View will exhibit the following behavior:

#### R17 (Requirement Type)
Selecting any element will show its properties in the Properties View, where it can be edited.
- Status: Done

#### R18 (Requirement Type)
Double-Clicking on a SpecHierarchy will open the corresponding Specification, with the clicked SpecHierarchy selected.
- Status: Done

### R20: Search-Conditions (Requirement Type)

#### R21 (Requirement Type)
In the following, we outline the various Conditions for the search box.

#### R22 (Requirement Type)
The Scope of attributes can be “internal” or “value”.
- Status: Done

#### R23 (Requirement Type)
Internal attributes are those defined by the ReqIF standard, e.g. Identifiable.identifier.
- Status: Done

#### R24 (Requirement Type)
Values are specific instances of Attributes that were set up by the user. They are identified in the form SPECTYPE.ATTRIBUTENAME.  Thus, as users create new SpecTypes and their attributes, so will the list of choices grow.
- Status: Done

#### R25 (Requirement Type)
The available criteria are determined by the Type.  We can class multiple attributes in one type (e.g. integer and real are both of type NUM).
- Status: Done

#### R26 (Requirement Type)
If an attribute is null or does not exist, then it is treated as if it was empty.
- Status: Done

#### R27 (Requirement Type)
Identifiable.identifier (STRING): Internal attribute
- Status: Done

#### R28 (Requirement Type)
Identifiable.lastChange (DATE): Internal attribute
- Status: Done

#### R29 (Requirement Type)
Identifiable.desc (STRING): Internal attribute
- Status: Done

#### R30 (Requirement Type)
Identifiable.longName (STRING) Internal attribute
- Status: Done

#### R31 (Requirement Type)
AttributeValueBoolean (BOOL): Value
- Status: Done

#### R32 (Requirement Type)
AttributeValueDate (DATE): Value
- Status: Done

#### R33 (Requirement Type)
AttributeValueEnumeration (ENUM): Value
- Status: Done

#### R34 (Requirement Type)
AttributeValueInteger (NUM): Value
- Status: Done

#### R35 (Requirement Type)
AttributeValueReal (NUM): Value
- Status: Done

#### R36 (Requirement Type)
AttributeValueString (STRING): Value
- Status: Done

#### R37 (Requirement Type)
AttributeValueXHTML (XHTML): Value
- Status: Done

#### R38 (Requirement Type)
The following table describes the various types.  Most types are straight forward, except XHTML.
- Status: Done

#### R39 (Requirement Type)
The XHTML operation is applied to the raw XHTML, including all tags (this allows searching for embedded URLs, for instance).  There is the additional option of “regexp plain”. In that case, the regular expression is applied to the plain text, with all tags stripped out.
- Status: Done

#### R40 (Requirement Type)
NOTE: We are considering to introduce a NEGATION flag for all conditions.  This would reduce the number of selectors, but of course not the number of overall options.
- Status: Won't implement

### R75: Operators for all (Requirement Type)

#### R76 (Requirement Type)
is set: If a non-null-value exists, return true.  Ignore default values (i.e. if there is a default value but no explicitly set one, return false).
- Status: Done

#### R77 (Requirement Type)
is not set: return true only if the attribute exisits, but is not set (irrespective of default value).
- Status: Done

### R41: Search-Conditions Interface (Requirement Type)

#### R42: String (Requirement Type)
- Status: Done

##### R43 (Requirement Type)
equal:one text field (if empty: false)
- Status: Done

##### R44 (Requirement Type)
not equal: one text field (if empty: true)
- Status: Done

##### R45 (Requirement Type)
contains: one text field (if empty: false)
- Status: Done

##### R46 (Requirement Type)
not contains: one text field (if empty: true)
- Status: Done

##### R47 (Requirement Type)
regexp: one text field (if empty: regexp applied to empty string)
- Status: Done

#### R48: Date (Requirement Type)
- Status: Done

##### R49 (Requirement Type)
is: one date selector (if empty: false)
- Status: Done

##### R50 (Requirement Type)
is not: one date selector (if empty: true)
- Status: Done

##### R51 (Requirement Type)
between: two date selectors (if empty: false)
- Status: Done

##### R52 (Requirement Type)
before: one date selector (if empty: false)
- Status: Done

##### R53 (Requirement Type)
after: one date selector (if empty: false)
- Status: Done

#### R54: Bool (Requirement Type)
- Status: Done

##### R55 (Requirement Type)
is: dropwdown: true/false (if empty: false)

#### R56: Number (Requirement Type)
- Status: Done

##### R57 (Requirement Type)
is: one number field (if empty: false)
- Status: Done

##### R58 (Requirement Type)
is not: one number field (if empty: true)
- Status: Done

##### R59 (Requirement Type)
between: two number fields (if empty: false)
- Status: Done

##### R60 (Requirement Type)
greater: one number field (if empty: false)
- Status: Done

##### R61 (Requirement Type)
smaller: one number field (if empty: false)
- Status: Done

#### R62: XHTML (Requirement Type)
- Status: Done

##### R63 (Requirement Type)
contains: one text field (if empty: false)
- Status: Done

##### R64 (Requirement Type)
not contains: one text field (if empty: true)
- Status: Done

##### R65 (Requirement Type)
regexp: one text field (if empty: regexp applied to empty string)
- Status: Done

##### R66 (Requirement Type)
regexp plain: one text field (if empty: regexp applied to empty string)
- Status: Done

#### R67: Enum (Requirement Type)
- Status: Done

##### R68 (Requirement Type)
equal: multiple choice (if empty: false, unless empty)
- Status: Done

##### R69 (Requirement Type)
not equal: multiple choice (if empty: true, unless empty)
- Status: Done

##### R70 (Requirement Type)
contains all: multiple choice (if empty: false, unless empty)
- Status: Done

##### R71 (Requirement Type)
contains any: multiple choice (if emtpy: false, unless empty)
- Status: Done

### R72: Documentation (Requirement Type)

#### R73 (Requirement Type)
Context-Sensitive Integration
- Status: Done

#### R74 (Requirement Type)
Help Content
- Status: Ready
